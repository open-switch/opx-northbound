module base-if-vlan {
    namespace "http://www.dellemc.com/networking/os10/base-if-vlan";

    prefix "base-if-vlan";

    import iana-if-type { prefix "ianaift"; }

    import ietf-interfaces {
        prefix "if";
    }
	
    import base-common {
        prefix "base-cmn";
    }

    organization "Dell EMC";
    contact "http://www.dell.com/support";

    description "This model augments the standard interface and adds Dell EMC specific
    				vlan extensions.";

    revision "2016-01-01" {
        description "Initial version.";
    }
	
    augment "/if:interfaces/if:interface" {
        when "if:type = 'ianaift:l2vlan' or if:type = 'ianaift:l3vlan'";

        leaf id {
            type base-cmn:vlan-id;
            description "the vlan id associated with interface";
        }	
    }
}
