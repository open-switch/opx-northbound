module base-interface-common {

    namespace "http://www.dellemc.com/networking/os10/base-interface-common";
    prefix "base-if";

    import iana-if-type { prefix "ianaift"; }
    import base-common { prefix "base-cmn"; }

    organization
        "Dell EMC";

    contact "http://www.dell.com/support";

    description
        "This module contains the collection of YANG definitions for
        managing interfaces";

    revision 2015-01-29 {
        description
            "Initial revision.";
    }

    identity null {
      base ianaift:iana-interface-type;
      description "Null interface type";
    }

    identity management {
      base ianaift:iana-interface-type;
      description "Management interface type";
    }

    identity cpu {
      base ianaift:iana-interface-type;
      description "CPU interface type";
    }
    typedef speed {
        description "Enumeration of port speed.";
        type enumeration {
            enum 0MBPS {
                value 0;
                description "0Mbps data rate.";
            }

            enum 10MBPS {
                value 1;
                description "10Mbps data rate.";
            }

            enum 100MBPS {
                value 2;
                description "100Mbps data rate.";
            }

            enum 1GIGE {
                value 3;
                description "1G data rate.";
            }

            enum 10GIGE {
                value 4;
                description "10G data rate.";
            }

            enum 25GIGE {
                value 5;
                description "25G data rate.";
            }

            enum 40GIGE {
                value 6;
                description "40G data rate.";
            }

            enum 100GIGE {
                value 7;
                description "100G data rate.";
            }

            enum AUTO {
                value 8;
                description "The speed is dependent on the media type.";
            }
            enum 20GIGE {
                value 9;
                description "20G data rate.";
            }
            enum 50GIGE {
                value 10;
                description "50G data rate.";
            }
            enum 200GIGE {
                value 11;
                description "200G data rate.";
            }
            enum 400GIGE {
                value 12;
                description "400G data rate.";
            }
            enum 4GFC {
                value 13;
                description "4G FC data rate.";
            }
            enum 8GFC {
                value 14;
                description "8G FC data rate.";
            }
            enum 16GFC {
                value 15;
                description "16G FC data rate.";
            }
            enum 32GFC {
                value 16;
                description "32G FC data rate.";
            }
        }
    }

    typedef mode {
        description "Enumeration of physical interface mode";
        type enumeration {
            enum MODE_NONE {
                value 1;
                description "";
            }

            enum MODE_L2 {
                value 2;
                description "The port only supports L2.";
            }

            enum MODE_L2HYBRID {
                value 3;
                description "The port supports L2 hybrid.";
            }

            enum MODE_L3 {
                value 4;
                description "The port only supports L3.";
            }

            enum MODE_L2DISABLED {
                value 5;
                description "This port is not in L2 Mode";
            }
        }
    }
    typedef lag-mode-type {
        description "LAG Mode";
      type enumeration {
        enum STATIC {
            value 1;
            description "";
        }

        enum DYNAMIC {
            value 2;
            description "";
        }
        }
    }

    typedef lacp-mode-type {
        description "LACP MODE";
        type enumeration {

        enum ACTIVE {
            value 1;
            description "";
        }

        enum PASSIVE {
            value 2;
            description "";
        }
      }
    }

    typedef vlan-type {
        description "VLAN-type type definition";

        type enumeration {
            enum DATA {
                value 1;
            }
            enum MANAGEMENT {
                value 2;
            }
        }
    }


    grouping physical-port-address {
        leaf unit-id {
           type uint32;
           description "The unit containing the front panel port";
        }

		leaf slot-id {
			type uint32;
			description "the slot id of the physical port.";
		}

        uses npu-port;
    }

    grouping npu-port {
        description "NAS npu port information.";
        leaf npu-id {
            type base-cmn:npu-id;
            description "This denotes the npu Id containing the physical port";
        }

        leaf  port-id {
            type base-cmn:npu-port-id;
            description "This denotes the port Id in the npu";
        }
    }

    grouping common {
        description "This is the generic port definition.  Can be reused by any generic interface object.";

        leaf switch-id {
            type base-cmn:logical-switch-id;
            description "Logical Switch ID";
        }
		uses npu-port;

    }

    grouping mac-learn-limit {

        description
            "List of Mac Learn Limit configuration";

        leaf learn-limit {
            type uint32;
            description "Maximum number of MACs allowed to be learned on an interace";
        }

        leaf dynamic {
            type boolean;
            default false;
            description "Whether the entry created is subject to aging.";
        }

        leaf station-move {
            type boolean;
            default false;
            description "Whether the station move is allowed or not";
        }

        leaf mac-sticky {
            type boolean;
            default false;
            description
                "If True then all dynamically learnt addresses will be converted into static MAC address
                and it will not be learnt/moved on other ports. Any new learnt MAC are also converted
                into sticky MAC address. Sticky flag takes precedence over dynamic";
        }


        leaf mll-violation-actions {
            description "Configurable mac learn limit (mll) actions when mac learn limit is violated";
            type enumeration {
                enum LOG {
                    value 1;
                    description "Send the Mac-learn-limit violation notification to syslog";
                }
                enum SHUTDOWN {
                    value 2;
                    description "Shutdown the Interface";
                }
            }
        }

        leaf msm-violation {
        	description "MAC station move (msm) violation actions.";
            type enumeration {
                enum LOG {
                    value 1;
                    description "Send the Mac-station-move-violation notification to syslog";
                }
                enum OFFENDING_SHUTDOWN {
                    value 2;
                    description "Shutdown the offending interface";
                }
                enum ORIGINAL_SHUTDOWN {
                    value 3;
                    description "Shutdown the original interface";
                }
                enum BOTH_SHUTDOWN {
                    value 4;
                    description "Disable both the interfaces";
                }
            }
        }
    }
  typedef phy-mode-type {
    type enumeration {
      enum ETHERNET {
        value 1;
      }
      enum FC {
        value 2;
      }
    }
  }
  grouping breakout-capabilities {
        list br-cap {
        key "phy-mode breakout-mode port-speed";
        description "List of breakout capabilities with max port speeds.";
            leaf phy-mode {
                type phy-mode-type;
                description " Physical layer mode , FC or Ethernet";
            }
            leaf breakout-mode {
                type base-cmn:breakout-type ;
                description "Breakout mode capability.";
            }
            leaf port-speed {
                type base-if:speed;
                description "Supported speed.";
            }
            leaf skip-ports {
                type uint32;
                description "Skip ports between two active port for the breakout mode";
            }
        }
    }


}
