module dell-base-if-common {
    namespace "http://www.dellemc.com/networking/os10/base/dell-base-if-common";

    prefix "dell-base-if-cmn";

    import ietf-interfaces {
        prefix "if";
    }
    import ietf-yang-types {
        prefix "yang";
    }
    import base-common {
        prefix "base-cmn";
    }

    import dell-interface {
        prefix "dell-if";
    }
    organization "Dell EMC";
    contact "http://www.dell.com/support";

    description "This model augments the standard interface and adds Dell EMC specific
                    extensions.  This model contains the entry point for the
                    interface object extensions.";

    revision "2018-05-08" {
        description "Added support for VLAN filtering object. This object helps to
                     get or set VLAN filtering feature on an interface";
        reference "IEEE 802.1Q";
    }

    revision "2018-01-22" {
        description "Augmented if/interfaces model from dell-interface to handle the
                     attributes augmented in dell-interface.yang";
    }

    revision "2017-10-10" {
        description "Add typedef for update type to use it for leaf list attribute type.
                     Add member-op attribute for rpc set-interface to handle leaf-list update";
    }

    revision "2016-01-01" {
        description "Initial version.";
    }


    augment "/if:interfaces/if:interface" {
        description "The following attributes are common to all interface types.";

        leaf if-index {
            type base-cmn:logical-ifindex;
            description "Can be used as an alternate to the name key field.  The if-index is the linux representation for the interface.";
        }

        leaf vlan-filter {
            type base-cmn:filter-type;
            default "INGRESS_ENABLE";
            description "Used to enable or disable VLAN filtering flag on an interface. By default, Ingress VLAN Filter is enabled";
        }
    }

    augment "/if:interfaces-state/if:interface" {
        leaf vlan-filter {
            type base-cmn:filter-type;
            description "Used to get the status of Interface VLAN filtering flag";
        }
    }

    augment "/if:interfaces-state/if:interface/if:statistics" {

        leaf time-stamp{
            type yang:timestamp;
            description "Timestamp at which stats are returned";
        }
    }

    typedef operation-type {
        description "Operation type of interface configuration";

        type enumeration {
            enum CREATE {
                value 1;
                description "Operation to create interface";
            }
            enum DELETE {
                value 2;
                description "Operation to delete interface";
            }
            enum UPDATE {
                value 3;
                description "Operation to update interface attributes";
            }
        }
    }
    typedef update-type {
        type enumeration {
            enum ADD {
                value 1;
                description "Operation to add member";
            }
            enum REMOVE {
                value 2;
                description "Operation to remove member";
            }
        }
    }


    rpc set-interface {
        description "This method is used to create, delete or set multiple types of interface. For
                create operation, mac address will be allocated if it is not given within input argument.
                Currently there is only one input argument which specified operation type, user should
                use attributes of the model of corresponding interface type as extra input.
                if:interface model is used as input for interface configuration.";

        // QUALIFIER  :  target
        // ========
        //
        // OBJ PATH : dell-base-if-cmn/set-interface
        // ========
        //
        // INPUT  :
        // =====
        // a) Explicit:
        //    --------
        //              dell-base-if-cmn/set-interface/input/operation (1=create, 2=delete, 3=update),
        //              dell-base-if-cmn/set-interface/input/member-op (1=add, 2=remove),
        // b) Implicit:
        //    --------
        //    Users could use additional attributes from other models (eg. if, base-if-phy etc.)
        //    Eg.
        //            	if/interfaces/interface/name,
        //             	if/interfaces/interface/type,
        //             	if/interfaces/interface/enabled,
        //             	if/interfaces/interface/mtu,
        //             	if/interfaces/interface/learn-mode,
        //             	if/interfaces/interface/tagging-mode(For Phy Interface Only),
        //             	if/interfaces/interface/speed(For Phy Interface Only),
        //             	if/interfaces/interface/auto-negotiation(For Phy Interface Only),
        //             	if/interfaces/interface/duplex(For Phy Interface Only),
        //             	if/interfaces/interface/eee(For Phy Interface Only),
        //             	if/interfaces/interface/fec(For Phy Interface Only),
        //             	if/interfaces/interface/oui(For Phy Interface Only),
        //             	if/interfaces/interface/type(For Phy Interface Only),
        //              Etc.
        // OUTPUT :
        // ======
        // a) Explicit:
        //    --------
        //	        None.
        // b) Implicit:
        //    -------
        //              dell-base-if-cmn/if/interfaces/interface/if-index.

        input {
            leaf operation {
                description "Specify operation type to configure interface.";
                type operation-type;
            }
            leaf member-op {
                description " Specify the operation type in case of member add or remove. This field is optional
                              and member list is considered a complete list in case if member-op is not present.";
                type update-type;
            }
        }
    }

    rpc get-mac-address {
        description "This method is used to get assgined mac address for different type of interfaces.
                User should give required attributes such as interface-name, type as input. The actual
                attributes needed depends on requested interface type";
    }

    augment "dell-if:clear-counters/dell-if:input" {

    }

    augment "dell-if:clear-eee-counters/dell-if:input" {

    }

    augment "/if:interfaces"{

    }
}
