module base-common {
  namespace "http://www.dellemc.com/networking/os10/base-common";
  prefix base-cmn;

  organization "Dell EMC";
  contact
    "http://www.dell.com/support";
  description
    "This module contains a collection of common YANG derived types used
     in other Base Yang modules.";

  revision 2015-09-24 {
    description
      "Added Enum values to breakout-mode";
  }
  revision 2015-05-27 {
    description
      "Phase 2 of clean-up work";
  }
  revision 2015-05-21 {
    description
      "Phase 1 of clean-up work";
  }
  revision 2015-04-03 {
    description
      "Added the opaque data types";
  }
  revision 2015-03-12 {
    description
      "Initial revision";
  }

  typedef logical-ifindex {
    type uint32;
    description
      "Uniquely identifies any interface system-wide including
       physical ports, LAG interfaces and Vlan interfaces";
  }

   typedef vni {
     type uint32 {
         range "1 .. 16777215";
     }
     description
       "This type denotes a VXLAN Network Identifier.
        It is 24 bits long. Hence 16 million such unique ID's are possible";
   }

   typedef filter-type {
       type enumeration {
           enum DISABLE {
               value 1;
               description "Operation to disable both ingress and egress filtering";
           }
           enum ENABLE {
               value 2;
               description "Operation to enable both ingress and egress filtering";
           }
           enum INGRESS_ENABLE {
               value 3;
               description "Operation to enable only ingress filtering";
           }
           enum EGRESS_ENABLE {
               value 4;
               description "Operation to enable only egress filtering";
           }
        }
    }


  typedef npu-id {
    type uint32;
    description
      "Uniquely identifies a Network Processing Unit hardware
       in the system";
  }

  typedef npu-port-id {
    type uint32;
    description
      "Identifies a port within a Network Processing Unit";
  }

  typedef logical-switch-id {
    type uint32;
    description
      "Logical Switch Identifier. Logical switch is a grouping
       of one or more NPU(s) in the system. Each NPU can belong
       to only one logical switch";
  }

  typedef vlan-id {
    type uint16 {
      range "1 .. 4094";
    }
    description
      "This type denotes a IEEE 802.1Q VLAN Identifier.";
    reference "IEEE 802.1Q";
  }

  typedef af-type {
    type enumeration {
      enum "inet" {
        /* Address family - IPv4 */
        value 2;
      }
      enum "inet6" {
        /* Address family - IPv6 */
        value 10;
      }
    }
    description
      "Address Family";
  }

  typedef traffic-path {
    type enumeration {
      enum "ingress" {
        value 1;
        description
          "Enable sampling on Ingress packets";
      }
      enum "egress" {
        value 2;
        description
          "Enable sampling of Egress packets";
      }
      enum "ingress-egress" {
        value 3;
        description
          "Enable sampling of Ingress and Egress packets";
      }
    }
    default "ingress-egress";
  }

  typedef fec-type {
    type enumeration {
      enum "auto" {
        value 1;
      }
      enum "off" {
        value 2;
      }
      enum "cl91-rs" {
        value 3;
      }
      enum "cl74-fc" {
        value 4;
      }
      enum "cl108-rs" {
        value 5;
      }
      enum "not-supported" {
        value 6;
      }
    }
  }

  typedef admin-status-type {
    type enumeration {
      enum "up" {
        value 1;
      }
      enum "down" {
        value 2;
      }
      enum "testing" {
        value 3;
      }
    }
  }

  typedef oper-status-type {
    type enumeration {
      enum "up" {
        value 1;
        description
          "Ready to pass packets.";
      }
      enum "down" {
        value 2;
        description
          "Entity is down.";
      }
      enum "testing" {
        value 3;
        description
          "In some test mode.  No operational packets can
           be passed.";
      }
      enum "unknown" {
        value 4;
        description
          "Status cannot be determined for some reason.";
      }
      enum "dormant" {
        value 5;
        description
          "Waiting for some external event.";
      }
      enum "not-present" {
        value 6;
        description
          "Some component (typically hardware) is missing.";
      }
      enum "lower-layer-down" {
        value 7;
        description
          "Down due to state of lower-layer interface(s).";
      }
      enum "fail" {
        value 8;
        description
          "The interface has an internal failure.";
      }
    }
  }

  typedef stat-type {
    type enumeration {
      enum "port-stat" {
        value 1;
      }
      enum "flow-stat" {
        value 2;
      }
      enum "prefix-stat" {
        value 3;
      }
      enum "queue-stat" {
        value 4;
      }
      enum "buffer-stat" {
        value 5;
      }
      enum "interface-stat" {
        value 6;
      }
    }
    description
      "various statistics type that can be supported with Flex Stat";
  }

  // @TODO : To be deprecated. Use IETF iana type
  typedef interface-type {
    type enumeration {
      enum "l3-port" {
        value 1;
      }
      enum "l2-port" {
        value 2;
      }
      enum "loopback" {
        value 3;
      }
      enum "null" {
        value 4;
      }
      enum "tunnel" {
        value 5;
      }
      enum "svi" {
        value 6;
      }
      enum "cpu" {
        value 7;
      }
      enum "management" {
        value 8;
      }
      enum "ethernet" {
        value 9;
      }
      enum "vlan" {
        value 10;
      }
      enum "lag" {
        value 11;
      }
      enum "vrf" {
        value 12;
      }
       enum "macvlan" {
         value 13;
       }
       enum "vxlan" {
         value 14;
       }
       enum "bridge" {
         value 15;
       }
       enum "vlan_subintf" {
         value 16;
       }

    }
    description
      "Enumeration of the various support interface types";
  }

  typedef encap-type {
    type enumeration {
      enum "tagged" {
        value 1;
      }
      enum "untagged" {
        value 2;
      }
      enum "prio-tagged" {
        value 3;
      }
    }
    description
      "Encapsulation types: need to add more types";
  }

  // @TODO : Check if needed.
  typedef lag-hash-type {
    type enumeration {
      enum "src-ip" {
        value 1;
      }
      enum "dest-ip" {
        value 2;
      }
      enum "src-dest-ip" {
        value 3;
      }
      enum "src-port" {
        value 4;
      }
    }
    description
      "lag hashing info types: Need to add more hash types";
  }

  // @TODO : To be deprecated. Use IETF iana type
  typedef tun-type {
    type enumeration {
      enum "ipv4-tunnel" {
        value 1;
      }
      enum "ipv6-tunnel" {
        value 2;
      }
      enum "gre-tunnel" {
        value 3;
      }
      enum "vxlan-tunnel" {
        value 4;
      }
      enum "nvgre-tunnel" {
        value 5;
      }
      enum "erspan-tunnel" {
        value 6;
      }
      enum "mpls-tunnel" {
        value 7;
      }
    }
    description
      "Encapsulation types: need to add more types";
  }

  typedef base-obj-id-type {
    type uint64;
    description
      "Common type for object IDs returned to Applications";
  }

  typedef qos-meter-opaque-data {
    type binary;
    description
      "Meter info opaque data blob that Application obtains from
       QoS module and passes to other Base modules.";
  }

  typedef qos-queue-opaque-data {
    type binary;
    description
      "Queue info opaque data blob that Application obtains from
       QoS module and passes to other Base modules.";
  }

  typedef mirror-opaque-data {
    type binary;
    description
      "Mirroring session opaque data blob that Application obtains from
       Mirroring module and passes to other Base modules.";
  }

  typedef lag-opaque-data {
    type binary;
    description
      "LAG opaque data blob that Application obtains from
       LAG module and passes to other Base modules.";
  }

  typedef ip-nexthop-group-opaque-data {
    type binary;
    description
      "IP Nexthop group info opaque data blob that Application obtains
       from Routing module and passes to other Base modules.";
  }

  typedef mirror-id {
    type uint32;
    description
      "Identifier of the NAS mirror-session";
  }

  typedef dot1p {
    type uint8 {range "0..7";}
    description
      "3-bit of priority field in 802.1Q header";
  }

  typedef traffic-class {
    type uint8;
    description
      "Traffic class, i.e. internal QoS level";
  }

  typedef loopback-type {
    type enumeration {
      enum "none" {
        value 1;
      }
      enum "phy" {
        value 2;
      }
      enum "mac" {
        value 3;
      }
    }
    description "Physical port's loopback modes";
  }
  typedef duplex-type {
    type enumeration {
      enum "full" {
        value 1;
      }
      enum "half" {
        value 2;
      }
      enum "auto" {
        value 3;
      }
    }
  }
  typedef breakout-type {
    /* Breakout NxM implies N logical interfaces derived from M front panel ports */
    type enumeration {
      enum DISABLED {
        value 1;
      }
      enum BREAKOUT_4x1 {
        value 2;
      }
      enum BREAKOUT_2x1 {
        value 3;
      }
      enum BREAKOUT_1x1 {
        value 4;
      }
      enum BREAKOUT_8x2 {
        value 5; /* 8 logical interfaces derived from 2 front panel ports */
      }
      enum BREAKOUT_2x2 {
        value 6; /* 2 logical interfaces derived from 2 front panel ports */
      }
      enum BREAKOUT_4x4 {
        value 7; /* 4 logical interfaces derived from 4 front panel ports */
      }
      enum BREAKOUT_2x4 {
        value 8; /* 2 logical interfaces derived from 4 front panel ports */
      }
      enum BREAKOUT_4x2 {
        value 9; /* 4 logical interfaces derived from 2 front panel ports */
      }
      enum BREAKOUT_UNKNOWN {
        value 10; /* The breakout mode cannot be determined */
 	description "breakout is not identified due to unknown reason(s).";
      }
      enum NO_BREAKOUT {
         value 11; /* Device does not breakout  */
 	description "breakout is not supported on the given port(s).";
      }

    }
  }
}
