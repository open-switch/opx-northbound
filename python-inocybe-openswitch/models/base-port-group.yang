module base-port-group {
    namespace "http://www.dellemc.com/networking/os10/dell-base-port-group";
    prefix "base-pg";

    import port-group { prefix "pg"; }

    organization "Dell EMC";
    contact "http://www.dell.com/support";

    description "This model contains Dell EMC specific port-group defintion and its attributes.";

    revision "2018-04-05" {
        description "Augmenting hybrid group config and state object.";
        reference "Network Platform Abstraction";
    }

    revision "2016-11-22" {
        description "Initial version.";
    }

    augment "/pg:port-groups/pg:port-group" {

    }

    augment "/pg:port-groups/pg:hybrid-group" {

    }

    augment "/pg:port-groups-state/pg:port-group-state" {
        leaf-list hwport-list {
            type uint32;
            description "List of hardware ports belonging to this port-group";
        }

        leaf-list front-panel-port {
            type uint32;
            description "list of the front panel port Ids associated with this port-group.";
        }
    }


    augment "/pg:port-groups-state/pg:hybrid-group-state" {
        leaf-list hwport-list {
            type uint32;
            description "List of hardware ports belonging to this port-group";
        }

        leaf-list front-panel-port {
            type uint32;
            description "list of the front panel port id's associated with this port-group.";
        }
    }

}
